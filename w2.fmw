FME workspace w2.fmw

Parameters:
- DestDataset_POSTGIS =
- DestDataset_POSTGIS_3 =
- SourceDataset_GEODATABASE_FILE =
- SourceDataset_SHAPEFILE =

Readers:
- SHAPEFILE_1: SHAPEFILE from $(SourceDataset_SHAPEFILE)
- GEODATABASE_FILE_1: GEODATABASE_FILE from $(SourceDataset_GEODATABASE_FILE)

Writers:
- POSTGIS_1: POSTGIS to $(DestDataset_POSTGIS)
- POSTGIS_2: POSTGIS to $(DestDataset_POSTGIS_3)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> AttributeFilter
AttributeFilter
    ATTR_NAME = FILE_NAME
    ATTR_VALUES = SOUTH_WALES_WEST_PER,SOUTH_WALES_CENTRAL_PER,SOUTH_WALES_EAST_PER,<Empty>,<Missing>,<Null>,<Unfiltered>
    SOUTH_WALES_WEST_PER -> Reprojector
    SOUTH_WALES_CENTRAL_PER -> Reprojector
    SOUTH_WALES_EAST_PER -> Reprojector
Reprojector
    DEST = LL-WGS84
    INTERPOLATION_TYPE_NAME = Nearest Neighbor
    RASTER_CELL_SIZE = Preserve Cells
    RASTER_TOLERANCE = 0.0
    REPROJECTED -> Clipper [CLIPPER]
Extend (reader GEODATABASE_FILE_1)
    attributes: OBJECTID integer, SHAPE_Length double, SHAPE_Area double
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Export (writer POSTGIS_1)
    INSIDE -> Extend (writer POSTGIS_1)
Extend (writer POSTGIS_1)
    attributes: objectid int4, shape_length float8, shape_area float8
Export (writer POSTGIS_1)
    attributes: name varchar(100), area_code varchar(3), descriptio varchar(50), file_name varchar(100), number int8, number0 int8, polygon_id int8, unit_id int8, code varchar(9), hectares float4, area float4, type_code varchar(2), descript0 varchar(25), type_cod0 varchar(3), descript1 varchar(36)
